[source: https://github.com/ICAO-TRIP-ISO-WG3/39794-5-AP/blob/main/ID-ICAO-ISO-IEC-39794-5-ed-1-v1.asn]

ID-ICAO-ISO-IEC-39794-5-ed-1-v1 { joint-iso-itu-t(2) international-organizations(23) icao(136) mrtd(1) iso-iec-39794(39794) part-5(5) ed-1(1) v1(1) iso-iec-39794-5(0) }

-- This ASN.1 module is derived from ISO-IEC-39794-5-ed-1-v1

-- Use of ISO/IEC copyright in this Schema is licensed for the purpose of 
-- developing, implementing, and using software based on this Schema, subject 
-- to the following conditions:
-- 
-- * Software developed from this Schema must retain the Copyright Notice, 
--   this list of conditions and the disclaimer below ("Disclaimer").
-- 
-- * Neither the name or logo of ISO or of IEC, nor the names of specific 
--   contributors, may be used to endorse or promote software derived from 
--   this Schema without specific prior written permission. 
-- 
-- * The software developer shall attribute the Schema to ISO/IEC and 
--   identify the ISO/IEC standard from which it is taken. Such attribution 
--   (e.g., "This software makes use of the Schema from ISO/IEC 39794-5 
--   within modifications permitted in the relevant ISO/IEC standard. 
--   Please reproduce this note if possible."), may be placed in the 
--   software itself or any other reasonable location.
-- 
-- The Disclaimer is:
-- THE SCHEMA ON WHICH THIS SOFTWARE IS BASED IS PROVIDED BY THE COPYRIGHT 
-- HOLDERS AND CONTRIBUTORS "AS IS" AND ANY EXPRESS OR IMPLIED WARRANTIES, 
-- INCLUDING, BUT NOT LIMITED TO, THE IMPLIED WARRANTIES OF MERCHANTABILITY 
-- AND FITNESS FOR A PARTICULAR PURPOSE ARE DISCLAIMED. IN NO EVENT SHALL 
-- THE COPYRIGHT OWNER OR CONTRIBUTORS BE LIABLE FOR ANY DIRECT, INDIRECT, 
-- INCIDENTAL, SPECIAL, EXEMPLARY, OR CONSEQUENTIAL DAMAGES (INCLUDING, BUT 
-- NOT LIMITED TO, PROCUREMENT OF SUBSTITUTE GOODS OR SERVICES; LOSS OF USE, 
-- DATA, OR PROFITS; OR BUSINESS INTERRUPTION) HOWEVER CAUSED AND ON ANY 
-- THEORY OF LIABILITY, WHETHER IN CONTRACT, STRICT LIABILITY, OR TORT 
-- (INCLUDING NEGLIGENCE OR OTHERWISE) ARISING IN ANY WAY OUT OF THE USE OF 
-- THE CODE COMPONENTS, EVEN IF ADVISED OF THE POSSIBILITY OF SUCH DAMAGE.

DEFINITIONS IMPLICIT TAGS ::= BEGIN

	IMPORTS 
		VersionBlock,
		CaptureDateTimeBlock,
		QualityBlocks,
		PADDataBlock,
		CoordinateCartesian2DUnsignedShortBlock,
		CoordinateCartesian3DUnsignedShortBlock,
		RegistryIdBlock,
		CertificationIdBlocks
	FROM ID-ICAO-ISO-IEC-39794-1-ed-1-v1;

	FaceImageDataBlock ::= [APPLICATION 5] SEQUENCE {
		versionBlock [0] VersionBlock,
		representationBlocks [1] RepresentationBlocks,
		...
	}

	RepresentationBlocks ::= SEQUENCE SIZE (1) OF RepresentationBlock

	RepresentationBlock ::= SEQUENCE {
		representationId [0] INTEGER (0..MAX),
		imageRepresentation [1] ImageRepresentation,
		captureDateTimeBlock [2] CaptureDateTimeBlock OPTIONAL,
		qualityBlocks [3] QualityBlocks OPTIONAL,
		padDataBlock [4] PADDataBlock OPTIONAL,
		sessionId [5] INTEGER (0..MAX) OPTIONAL,
		derivedFrom [6] INTEGER (0..MAX) OPTIONAL,
		captureDeviceBlock [7] CaptureDeviceBlock OPTIONAL,
		identityMetadataBlock [8] IdentityMetadataBlock OPTIONAL,
		landmarkBlocks [9] LandmarkBlocks OPTIONAL,
		...
	}

	CaptureDeviceBlock ::= SEQUENCE {
		modelIdBlock [0] RegistryIdBlock OPTIONAL,
		certificationIdBlocks [1] CertificationIdBlocks OPTIONAL,
		...
	}

	IdentityMetadataBlock ::= SEQUENCE {
		gender [0] Gender OPTIONAL,
		eyeColour [1] EyeColour OPTIONAL,
		hairColour [2] HairColour OPTIONAL,
		subjectHeight [3] SubjectHeight OPTIONAL,
		propertiesBlock [4] PropertiesBlock OPTIONAL,
		expressionBlock [5] ExpressionBlock OPTIONAL,
		poseAngleBlock [6] PoseAngleBlock OPTIONAL,
		...
	}

	GenderCode ::= ENUMERATED {
		other (1),
		male (2),
		female (3)
	}

	GenderExtensionBlock ::= SEQUENCE {
		fallback [0] GenderCode,
		...
	}

	Gender ::= CHOICE {	
		extensionBlock [1] GenderExtensionBlock
	}

	EyeColourCode ::= ENUMERATED {
		unknown (0),
		other (1),
		black (2),
		blue (3),
		brown (4),
		grey (5),
		green (6),
		hazel (7),
		multi-coloured (8),
		pink (9)
	}

	EyeColourExtensionBlock ::= SEQUENCE {
		fallback [0] EyeColourCode,
		...
	}

	EyeColour ::= CHOICE {	
		extensionBlock [1] EyeColourExtensionBlock
	}

	HairColourCode ::= ENUMERATED {
		unknown (0),
		other (1),
		bald (2),
		black (3),
		blonde (4),
		brown (5),
		grey (6),
		white (7),
		red (8),
		knownColoured (9)
	}

	HairColourExtensionBlock ::= SEQUENCE {
		fallback [0] HairColourCode,
		...
	}

	HairColour ::= CHOICE {	
		extensionBlock [1] HairColourExtensionBlock
	}

	SubjectHeight ::= INTEGER (1..65535)

	PropertiesBlock ::= SEQUENCE {
		glasses [0] BOOLEAN OPTIONAL,
		moustache [1] BOOLEAN OPTIONAL,
		beard [2] BOOLEAN OPTIONAL,
		teethVisible [3] BOOLEAN OPTIONAL,
		pupilOrIrisNotVisible [4] BOOLEAN OPTIONAL,
		mouthOpen [5] BOOLEAN OPTIONAL,
		leftEyePatch [6] BOOLEAN OPTIONAL,
		rightEyePatch [7] BOOLEAN OPTIONAL,
		darkGlasses [8] BOOLEAN OPTIONAL,
		biometricAbsent [9] BOOLEAN OPTIONAL,
		headCoveringsPresent [10] BOOLEAN OPTIONAL,
		...
	}

	ExpressionBlock ::= SEQUENCE {
		neutral [0] BOOLEAN OPTIONAL,
		smile [1] BOOLEAN OPTIONAL,
		raisedEyebrows [2] BOOLEAN OPTIONAL,
		eyesLookingAwayFromTheCamera [3] BOOLEAN OPTIONAL,
		squinting [4] BOOLEAN OPTIONAL,
		frowning [5] BOOLEAN OPTIONAL,
		...
	}

	PoseAngleBlock ::= SEQUENCE {
		yawAngleBlock [0] AngleDataBlock OPTIONAL,
		pitchAngleBlock [1] AngleDataBlock OPTIONAL,
		rollAngleBlock [2] AngleDataBlock OPTIONAL
	}

	AngleDataBlock ::= SEQUENCE {
		angleValue [0] AngleValue,
		angleUncertainty [1] AngleUncertainty OPTIONAL,
		...
	}

	AngleValue ::= INTEGER (-180..180)

	AngleUncertainty ::= INTEGER (0..180)

	LandmarkBlocks ::= SEQUENCE OF LandmarkBlock

	LandmarkBlock ::= SEQUENCE {
		landmarkKind [0] LandmarkKind,
		landmarkCoordinates [1] LandmarkCoordinates OPTIONAL,
		...
	}
	
	LandmarkKind ::= CHOICE {
		base [0] LandmarkKindBase,
		extensionBlock [1] LandmarkKindExtensionBlock
	}

	LandmarkKindBase ::= CHOICE {
		mpeg4FeaturePoint [0] MPEG4FeaturePoint,
		anthropometricLandmark [1] AnthropometricLandmark
	}

	LandmarkKindExtensionBlock ::= SEQUENCE {
		...
	}
	
	MPEG4FeaturePointCode ::= ENUMERATED {
		mpeg4PointCode-02-01 (0),
		mpeg4PointCode-02-02 (1),
		mpeg4PointCode-02-03 (2),
		mpeg4PointCode-02-04 (3),
		mpeg4PointCode-02-05 (4),
		mpeg4PointCode-02-06 (5),
		mpeg4PointCode-02-07 (6),
		mpeg4PointCode-02-08 (7),
		mpeg4PointCode-02-09 (8),
		mpeg4PointCode-02-10 (9),
		mpeg4PointCode-02-11 (10),
		mpeg4PointCode-02-12 (11),
		mpeg4PointCode-02-13 (12),
		mpeg4PointCode-02-14 (13),
		mpeg4PointCode-03-01 (14),
		mpeg4PointCode-03-02 (15),
		mpeg4PointCode-03-03 (16),
		mpeg4PointCode-03-04 (17),
		mpeg4PointCode-03-05 (18),
		mpeg4PointCode-03-06 (19),
		mpeg4PointCode-03-07 (20),
		mpeg4PointCode-03-08 (21),
		mpeg4PointCode-03-09 (22),
		mpeg4PointCode-03-10 (23),
		mpeg4PointCode-03-11 (24),
		mpeg4PointCode-03-12 (25),
		mpeg4PointCode-03-13 (26),
		mpeg4PointCode-03-14 (27),
		mpeg4PointCode-04-01 (28),
		mpeg4PointCode-04-02 (29),
		mpeg4PointCode-04-03 (30),
		mpeg4PointCode-04-04 (31),
		mpeg4PointCode-04-05 (32),
		mpeg4PointCode-04-06 (33),
		mpeg4PointCode-05-01 (34),
		mpeg4PointCode-05-02 (35),
		mpeg4PointCode-05-03 (36),
		mpeg4PointCode-05-04 (37),
		mpeg4PointCode-06-01 (38),
		mpeg4PointCode-06-02 (39),
		mpeg4PointCode-06-03 (40),
		mpeg4PointCode-06-04 (41),
		mpeg4PointCode-07-01 (42),
		mpeg4PointCode-08-01 (43),
		mpeg4PointCode-08-02 (44),
		mpeg4PointCode-08-03 (45),
		mpeg4PointCode-08-04 (46),
		mpeg4PointCode-08-05 (47),
		mpeg4PointCode-08-06 (48),
		mpeg4PointCode-08-07 (49),
		mpeg4PointCode-08-08 (50),
		mpeg4PointCode-08-09 (51),
		mpeg4PointCode-08-10 (52),
		mpeg4PointCode-09-01 (53),
		mpeg4PointCode-09-02 (54),
		mpeg4PointCode-09-03 (55),
		mpeg4PointCode-09-04 (56),
		mpeg4PointCode-09-05 (57),
		mpeg4PointCode-09-06 (58),
		mpeg4PointCode-09-07 (59),
		mpeg4PointCode-09-08 (60),
		mpeg4PointCode-09-09 (61),
		mpeg4PointCode-09-10 (62),
		mpeg4PointCode-09-11 (63),
		mpeg4PointCode-09-12 (64),
		mpeg4PointCode-09-13 (65),
		mpeg4PointCode-09-14 (66),
		mpeg4PointCode-09-15 (67),
		mpeg4PointCode-10-01 (68),
		mpeg4PointCode-10-02 (69),
		mpeg4PointCode-10-03 (70),
		mpeg4PointCode-10-04 (71),
		mpeg4PointCode-10-05 (72),
		mpeg4PointCode-10-06 (73),
		mpeg4PointCode-10-07 (74),
		mpeg4PointCode-10-08 (75),
		mpeg4PointCode-10-09 (76),
		mpeg4PointCode-10-10 (77),
		mpeg4PointCode-11-01 (78),
		mpeg4PointCode-11-02 (79),
		mpeg4PointCode-11-03 (80),
		mpeg4PointCode-11-04 (81),
		mpeg4PointCode-11-05 (82),
		mpeg4PointCode-11-06 (83),
		mpeg4PointCode-12-01 (84),
		mpeg4PointCode-12-02 (85),
		mpeg4PointCode-12-03 (86),
		mpeg4PointCode-12-04 (87)
	}

	MPEG4FeaturePointExtensionBlock ::= SEQUENCE {
		fallback [0] MPEG4FeaturePointCode,
		...
	}

	MPEG4FeaturePoint ::= CHOICE {	
		extensionBlock [1] MPEG4FeaturePointExtensionBlock
	}
	
	AnthropometricLandmark ::= CHOICE {
		base [0] AnthropometricLandmarkBase,
		extensionBlock [1] AnthropometricLandmarkExtensionBlock
	}

	AnthropometricLandmarkBase ::= CHOICE {
		anthropometricLandmarkName [0] AnthropometricLandmarkName,
		anthropometricLandmarkPointName [1] AnthropometricLandmarkPointName,
		anthropometricLandmarkPointId [2] AnthropometricLandmarkPointId
	}

	AnthropometricLandmarkExtensionBlock ::= SEQUENCE {
		...
	}

	AnthropometricLandmarkNameCode ::= ENUMERATED {
		vertex                      (0),
		glabella                    (1),
		opisthocranion              (2),
		eurionLeft                  (3),
		eurionRight                 (4),
		frontotemporaleLeft         (5),
		frontotemporaleRight        (6),
		trichion                    (7),
		zygionLeft                  (8),
		zygionRight                 (9),
		gonionLeft                  (10),
		gonionRight                 (11),
		sublabiale                  (12),
		pogonion                    (13),
		menton                      (14),
		condylionLateraleLeft       (15),
		condylionLateraleRight      (16),
		endocanthionLeft            (17),
		endocanthionRight           (18),
		exocanthionLeft             (19),
		exocanthionRight            (20),
		centerPointOfPupilLeft      (21),
		centerPointOfPupilRight     (22),
		orbitaleLeft                (23),
		orbitaleRight               (24),
		palpebraleSuperiusLeft      (25),
		palpebraleSuperiusRight     (26),
		palpebraleInferiusLeft      (27),
		palpebraleInferiusRight     (28),
		orbitaleSuperiusLeft        (29),
		orbitaleSuperiusRight       (30),
		superciliareLeft            (31),
		superciliareRight           (32),
		nasion                      (33),
		sellion                     (34),
		alareLeft                   (35),
		alareRight                  (36),
		pronasale                   (37),
		subnasale                   (38),
		subalare                    (39),
		alarCurvatureLeft           (40),
		alarCurvatureRight          (41),
		maxillofrontale             (42),
		christaPhiltraLandmarkLeft  (43),
		christaPhiltraLandmarkRight (44),
		labialeSuperius             (45),
		labialeInferius             (46),
		cheilionLeft                (47),
		cheilionRight               (48),
		stomion                     (49),
		superauraleLeft             (50),
		superauraleRight            (51),
		subauraleLeft               (52),
		subauraleRight              (53),
		preaurale                   (54),
		postaurale                  (55),
		otobasionSuperiusLeft       (56),
		otobasionSuperiusRight      (57),
		otobasionInferius           (58),
		porion                      (59),
		tragion                     (60)
	}

	AnthropometricLandmarkNameExtensionBlock ::= SEQUENCE {
		fallback [0] AnthropometricLandmarkNameCode,
		...
	}

	AnthropometricLandmarkName ::= CHOICE {	
		extensionBlock [1] AnthropometricLandmarkNameExtensionBlock
	}

	AnthropometricLandmarkPointNameCode ::= ENUMERATED {
		pointCode-01-01 (0),
		pointCode-01-02 (1),
		pointCode-01-05 (2),
		pointCode-01-06 (3),
		pointCode-01-07 (4),
		pointCode-01-08 (5),
		pointCode-01-09 (6),
		pointCode-02-01 (7),
		pointCode-02-02 (8),
		pointCode-02-03 (9),
		pointCode-02-04 (10),
		pointCode-02-05 (11),
		pointCode-02-06 (12),
		pointCode-02-07 (13),
		pointCode-02-09 (14),
		pointCode-02-10 (15),
		pointCode-03-01 (16),
		pointCode-03-02 (17),
		pointCode-03-03 (18),
		pointCode-03-04 (19),
		pointCode-03-05 (20),
		pointCode-03-06 (21),
		pointCode-03-07 (22),
		pointCode-03-08 (23),
		pointCode-03-09 (24),
		pointCode-03-10 (25),
		pointCode-03-11 (26),
		pointCode-03-12 (27),
		pointCode-04-01 (28),
		pointCode-04-02 (29),
		pointCode-04-03 (30),
		pointCode-04-04 (31),
		pointCode-05-01 (32),
		pointCode-05-02 (33),
		pointCode-05-03 (34),
		pointCode-05-04 (35),
		pointCode-05-06 (36)
	}

	AnthropometricLandmarkPointNameExtensionBlock ::= SEQUENCE {
		fallback [0] AnthropometricLandmarkPointNameCode,
		...
	}

	AnthropometricLandmarkPointName ::= CHOICE {	
		extensionBlock [1] AnthropometricLandmarkPointNameExtensionBlock
	}

	AnthropometricLandmarkPointIdCode ::= ENUMERATED {
		v         (0),
		g         (1),
		op        (2),
		eu-left   (3),
		eu-right  (4),
		ft-left   (5),
		ft-right  (6),
		tr        (7),
		zy-left   (8),
		zy-right  (9),
		go-left   (10),
		go-right  (11),
		sl        (12),
		pg        (13),
		gn        (14),
		cdl-left  (15),
		cdl-right (16),
		en-left   (17),
		en-right  (18),
		ex-left   (19),
		ex-right  (20),
		p-left    (21),
		p-right   (22),
		or-left   (23),
		or-right  (24),
		ps-left   (25),
		ps-right  (26),
		pi-left   (27),
		pi-right  (28),
		os-left   (29),
		os-right  (30),
		sci-left  (31),
		sci-right (32),
		n         (33),
		se        (34),
		al-left   (35),
		al-right  (36),
		prn       (37),
		sn        (38),
		sbal      (39),
		ac-left   (40),
		ac-right  (41),
		mf-left   (42),
		mf-right  (43),
		cph-left  (44),
		cph-right (45),
		ls        (46),
		li        (47),
		ch-left   (48),
		ch-right  (49),
		sto       (50),
		sa-left   (51),
		sa-right  (52),
		sba-left  (53),
		sba-right (54),
		pra-left  (55),
		pra-right (56),
		pa        (57),
		obs-left  (58),
		obs-right (59),
		obi       (60),
		po        (61),
		t         (62)
	}

	AnthropometricLandmarkPointIdExtensionBlock ::= SEQUENCE {
		fallback [0] AnthropometricLandmarkPointIdCode,
		...
	}

	AnthropometricLandmarkPointId ::= CHOICE {	
		extensionBlock [1] AnthropometricLandmarkPointIdExtensionBlock
	}

	LandmarkCoordinates ::= CHOICE {
		base [0] LandmarkCoordinatesBase,
		extensionBlock [1] LandmarkCoordinatesExtensionBlock
	}

	LandmarkCoordinatesBase ::= CHOICE {
		coordinateCartesian2DBlock [0] CoordinateCartesian2DUnsignedShortBlock,
		coordinateTextureImageBlock [1] CoordinateTextureImageBlock,
		coordinateCartesian3DBlock [2] CoordinateCartesian3DUnsignedShortBlock
	}

	LandmarkCoordinatesExtensionBlock ::= SEQUENCE {
		...
	}

	CoordinateTextureImageBlock ::= SEQUENCE {
		uInPixel [0] INTEGER (0..MAX),
		vInPixel [1] INTEGER (0..MAX)
	}

	ImageRepresentation ::= CHOICE {
		base [0] ImageRepresentationBase,
		extensionBlock [1] ImageRepresentationExtensionBlock
	}

	ImageRepresentationBase ::= CHOICE {	
		imageRepresentation2DBlock [0] ImageRepresentation2DBlock
	}

	ImageRepresentationExtensionBlock ::= SEQUENCE {
		...
	}

	ImageRepresentation2DBlock ::= SEQUENCE {
		representationData2D [0] OCTET STRING,
		imageInformation2DBlock [1] ImageInformation2DBlock,
		captureDevice2DBlock [2] CaptureDevice2DBlock OPTIONAL,
		...
	}
	
	CaptureDevice2DBlock ::= SEQUENCE {
		captureDeviceSpectral2DBlock [0] CaptureDeviceSpectral2DBlock OPTIONAL,
		captureDeviceTechnologyId2D [1] CaptureDeviceTechnologyId2D OPTIONAL,
		...
	}

	CaptureDeviceSpectral2DBlock ::= SEQUENCE {
		whiteLight [0] BOOLEAN OPTIONAL,
		nearInfrared [1] BOOLEAN OPTIONAL,
		thermal [2] BOOLEAN OPTIONAL,
		...
	}

	CaptureDeviceTechnologyId2DCode ::= ENUMERATED {
		unknown (0),
		staticPhotographFromUnknownSource (1),
		staticPhotographFromDigitalStillImageCamera (2),
		staticPhotographFromScanner (3),
		videoFrameFromUnknownSource (4),
		videoFrameFromAnalogueVideoCamera (5),
		videoFrameFromDigitalVideoCamera (6)
	}

	CaptureDeviceTechnologyId2DExtensionBlock ::= SEQUENCE {
		fallback [0] CaptureDeviceTechnologyId2DCode,
		...
	}

	CaptureDeviceTechnologyId2D ::= CHOICE {	
		extensionBlock [1] CaptureDeviceTechnologyId2DExtensionBlock
	}

	ImageInformation2DBlock ::= SEQUENCE {
		imageDataFormat [0] ImageDataFormat,
		faceImageKind2D [1] FaceImageKind2D OPTIONAL,
		postAcquisitionProcessingBlock [2] PostAcquisitionProcessingBlock OPTIONAL,
		lossyTransformationAttempts [3] LossyTransformationAttempts OPTIONAL,
		cameraToSubjectDistance [4] CameraToSubjectDistance OPTIONAL,
		sensorDiagonal [5] SensorDiagonal OPTIONAL,
		lensFocalLength [6] LensFocalLength OPTIONAL,
		imageSizeBlock [7] ImageSizeBlock OPTIONAL,
		imageFaceMeasurementsBlock [8] ImageFaceMeasurementsBlock OPTIONAL,
		imageColourSpace [9] ImageColourSpace OPTIONAL,
		referenceColourMappingBlock [10] ReferenceColourMappingBlock OPTIONAL,
		...
	}

	FaceImageKind2DCode ::= ENUMERATED {
		mrtd (0)
	}

	FaceImageKind2DExtensionBlock ::= SEQUENCE {
		fallback [0] FaceImageKind2DCode,
		...
	}

	FaceImageKind2D ::= CHOICE {	
		extensionBlock [1] FaceImageKind2DExtensionBlock
	}

	PostAcquisitionProcessingBlock ::= SEQUENCE {
		rotated [0] BOOLEAN OPTIONAL,
		cropped [1] BOOLEAN OPTIONAL,
		downSampled [2] BOOLEAN OPTIONAL,
		whiteBalanceAdjusted [3] BOOLEAN OPTIONAL,
		multiplyCompressed [4] BOOLEAN OPTIONAL,
		interpolated [5] BOOLEAN OPTIONAL,
		contrastStretched [6] BOOLEAN OPTIONAL,
		poseCorrected [7] BOOLEAN OPTIONAL,
		multiViewImage [8] BOOLEAN OPTIONAL,
		ageProgressed [9] BOOLEAN OPTIONAL,
		superResolutionProcessed [10] BOOLEAN OPTIONAL,
		normalised [11] BOOLEAN OPTIONAL,
		...
	}

	LossyTransformationAttemptsCode ::= ENUMERATED {
		unknown (0),
		zero (1),
		one (2),
		moreThanOne (3)
	}

	LossyTransformationAttemptsExtensionBlock ::= SEQUENCE {
		fallback [0] LossyTransformationAttemptsCode,
		...
	}

	LossyTransformationAttempts ::= CHOICE {	
		extensionBlock [1] LossyTransformationAttemptsExtensionBlock
	}

	ImageDataFormatCode ::= ENUMERATED {
		
		jpeg (2),
		jpeg2000Lossy (3),
		jpeg2000Lossless (4)
	}

	ImageDataFormatExtensionBlock ::= SEQUENCE {
		...
	}

	ImageDataFormat ::= CHOICE {		code [0] ImageDataFormatCode,
		extensionBlock [1] ImageDataFormatExtensionBlock
	}

	CameraToSubjectDistance ::= INTEGER (0..50000)

	SensorDiagonal ::= INTEGER (0..2000)

	LensFocalLength ::= INTEGER (0..2000)

	ImageSizeBlock ::= SEQUENCE {
		width [0] ImageSize,
		height [1] ImageSize
	}

	ImageSize ::= INTEGER (0..65535)
	
	ImageFaceMeasurementsBlock ::= SEQUENCE {
		imageHeadWidth [0] INTEGER (0..MAX) OPTIONAL,
		imageInterEyeDistance [1] INTEGER (0..MAX) OPTIONAL,
		imageEyeToMouthDistance [2] INTEGER (0..MAX) OPTIONAL,
		imageHeadLength [3] INTEGER (0..MAX) OPTIONAL,
		...
	}

	ImageColourSpaceCode ::= ENUMERATED {
		unknown (0),
		other (1),
		rgb24Bit (2),
		rgb48Bit (3),
		yuv422 (4),
		greyscale8Bit (5),
		greyscale16Bit (6)
	}

	ImageColourSpaceExtensionBlock ::= SEQUENCE {
		fallback [0] ImageColourSpaceCode,
		...
	}

	ImageColourSpace ::= CHOICE {	
		extensionBlock [1] ImageColourSpaceExtensionBlock
	}

	ReferenceColourMappingBlock ::= SEQUENCE {
		referenceColourSchema [0] OCTET STRING OPTIONAL,
		referenceColourDefinitionAndValueBlocks [1] ReferenceColourDefinitionAndValueBlocks OPTIONAL,
		...
	}

	ReferenceColourDefinitionAndValueBlocks ::= SEQUENCE OF ReferenceColourDefinitionAndValueBlock

	ReferenceColourDefinitionAndValueBlock ::= SEQUENCE {
		referenceColourDefinition [0] OCTET STRING OPTIONAL,
		referenceColourValue [1] OCTET STRING OPTIONAL,
		...
	}

	

END
